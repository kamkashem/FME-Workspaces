FME workspace verkeersbesluiten.fmw
Title: Verkeersbesluiten
Description: Verkeersbesluiten worden digitaal bekend gemaakt via een officiële publicatie in de Staatscourant. De collectie officiële publicaties wordt als open data ontsloten via de open data webservice van Overheid.nl Deze workspace harvest de verkeersbesluiten van de provincie Groningen.
History: 18-2-2018,Willy Tadema,

Parameters:
- MaxAantalRecords = 1000   # Maximum aantal records in reponse
- Query = (keyword=verkeersbesluit) and (creator=groningen) and (organisationType=Provincie)

Creator
    NUM = 1
    GEOMTYPE = Geometry Object
    CREATED -> HTTPCaller
Note: Request aan zoekdienst van Overheid.nl
HTTPCaller
    ADDITIONAL_URL_PARAMETERS = version;1.2 operation;searchRetrieve x-connection;oep startRecord;1 maximumRecords;$(MaxAantalRecords) query;$(Query)
    ERROR_ATTR = _error
    FILE_TYPE = <Auto Detect from HTTP Headers>
    TARGET_ATTR_ENCODING = auto-detect
    VERIFY_SSL_CERTIFICATES = Yes
    TRANSFER_TIMEOUT_LENGTH = 90
    SAVE_FILE = Attribute
    FOLLOW_REDIRECTS = Yes
    TARGET_URL = http://zoekdienst.overheid.nl/sru/Search?
    STATUS_CODE_ATTR = _http_status_code
    RESPONSE_HEADER_LIST_ATTR = _headers
    TARGET_ATTR = _response_body
    HTTP_METHOD = GET
    USE_COOKIES = No
    CONNECTION_TIMEOUT_LENGTH = 60
    -> XSLTProcessor
    -> XMLXQueryExtractor
Note: Transformeren van de API response m.b.v. een XSL style sheet
XSLTProcessor
    RESULTS_TYPE = Results in Attribute
    ATTRIBUTE_RESULTS = _result
    CONFIGURATION_TYPE = Embedded Stylesheet
    XML_INPUT_TYPE = Attribute with XML Document
    ATTRIBUTE_XML = _response_body
    EMBEDDED_STYLESHEET:
      <xsl:stylesheet version="1.0"
          xmlns:xsl="http://www.w3.org/1999/XSL/Transform"
          xmlns:srw="http://www.loc.gov/zing/srw/"
          xmlns:sru="http://standaarden.overheid.nl/sru"
          xmlns:dcterms="http://purl.org/dc/terms/"
          xmlns:overheid="http://standaarden.overheid.nl/owms/terms/"
          xmlns:overheidop="http://standaarden.overheid.nl/product/terms/"
          xmlns:overheidvb="http://standaarden.overheid.nl/vb/terms">

        <xsl:strip-space elements="*"/>
        <xsl:output method="xml" indent="yes"/>

        <xsl:template match="@*|node()">
          <xsl:apply-templates select="@*|node()"/>
        </xsl:template>

        <xsl:template match="srw:searchRetrieveResponse">
          <verkeersbesluiten>
            <xsl:apply-templates/>
          </verkeersbesluiten>
        </xsl:template>

        <xsl:template match="sru:gzd">
          <verkeersbesluit>
            <xsl:apply-templates/>
          </verkeersbesluit>
        </xsl:template>

        <xsl:template match="overheidop:owmskern">
          <titel1><xsl:value-of select="dcterms:title"/></titel1>
          <locatie><xsl:value-of select="dcterms:spatial"/></locatie>
        </xsl:template>

        <xsl:template match="overheidop:owmsmantel">
          <titel2><xsl:value-of select="dcterms:alternative"/></titel2>
        </xsl:template>

        <xsl:template match="sru:enrichedData">
          <url><xsl:value-of select="sru:url"/></url>
        </xsl:template>

      </xsl:stylesheet>
    TRANSFORMED -> XMLFragmenter
XMLFragmenter
    NEW_ATTRIBUTES = titel1 titel2 locatie url
    XML_SOURCE_TYPE = Attribute with XML document
    FEATURE_TYPES_FORMAT_NAME = XML
    MERGE_ATTRS = No
    ATTRIBUTE_XML = _result
    EMBEDDED_EXPRESSIONS = verkeersbesluiten/verkeersbesluit
    FLATTEN_OPTIONS = <structure separator="." map-empty-elements="yes" matched-prefix="attributes" matched-attributes="yes" cardinality="+{?}" structure-prefix="" child-position-attribute="" except-expression="" ui-mode="basic" matched-ancestor-attributes=""/>
    FRAGMENTS -> AttributeCreator
GeometryReplacer
    SOURCE = @Value(wkt)
    KIND_LONG = OGC Well Known Text
    REMOVE_ATTRIBUTE = Yes
    OGC_WKT_PRECISION_DISPLAY = 64-bit
    -> AttributeRemover
AttributeRemover
    REMOVE_ATTRS = locatie,locatie_preprocessed
    -> Verkeersbesluiten_gekoppeld_aan_de_kaart
Verkeersbesluiten_gekoppeld_aan_de_kaart: Inspector
Note: Selecteren van attribuutwaarde m.b.v. XQuery
XMLXQueryExtractor
    XML_ATTR = _response_body
    XML_REMOVE_SOURCE_ATTR = No
    QUERY_EXPR:
      declare namespace srw="http://www.loc.gov/zing/srw/";
      //srw:numberOfRecords/text()
    XQUERY_TYPE = XQuery expression
    RESULT_TYPE_NAME = Single value
    RESULT_ATTRIBUTE = AantalRecords
    XML_TYPE = Attribute specifying XML
    WRITE_XML_HEADER = No
    QUERY_RESULTS -> Tester
Tester
    TEST_DESCRIPTION = ""
    BOOL_OP = OR
    TEST_MODE = Automatic
    TEST_CLAUSE = TEST @Value(AantalRecords) > $(MaxAantalRecords)
    PASSED -> MessageLogger
Note: Warning genereren als het aantal besluiten in de response gelijk is aan / het maximum aantal besluiten dat geretourneerd wordt
MessageLogger
    MESSAGE = Let op: Niet alle records die voldoen aan het query-filter worden geretourneerd! Alleen de eerste $(MaxAantalRecords).
    TYPE = WARN

Bookmark: Transformatie geometrie naar WKT
AttributeCreator
    ATTR_TABLE = SET_TO locatie_preprocessed = @Trim(@ReplaceRegEx(@Value(locatie),[^(0-9{6}|\s|\$%\$)],""))
    -> StringReplacer
StringReplacer
    SRC_ATTRS = locatie_preprocessed
    CASE = NO
    FIND_TEXT = (\$%\$){1,}$
    REGEXP = YES
    NO_MATCH = _FME_NO_OP_
    -> AttributeManager
AttributeManager
    ATTR_TABLE:
      REMOVE xml_fragment
      REMOVE xml_id
      REMOVE xml_matched_element
      REMOVE xml_parent_id
      REMOVE xml_parent_child_pos
      SET_TO wkt = FME_CONDITIONAL:DEFAULT_VALUE'_FME_NO_OP_'BOOL_OP;OR;COMPOSITE_TEST;<Unused>;TEST @Evaluate(@StringLength(@Value(locatie_preprocessed))) = 13'POINT(@ReplaceString(@Value(locatie_preprocessed),"%$%",","))'BOOL_OP;OR;COMPOSITE_TEST;<Unused>;TEST @Evaluate(@StringLength(@Value(locatie_preprocessed))) > 13'LINESTRING(@ReplaceString(@Value(locatie_preprocessed),"$%$",","))'FME_NUM_CONDITIONS3___
    -> GeometryReplacer
