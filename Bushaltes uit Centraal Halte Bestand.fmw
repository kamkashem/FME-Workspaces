FME workspace Bushaltes uit Centraal Halte Bestand.fmw
Startup Python:
      import os, datetime, urllib, gzip, shutil

      filename = 'ExportCHB' + datetime.datetime.now().strftime("%Y%m%d") + '010001.xml.gz'
      url = 'http://data.ndovloket.nl/haltes/' + filename
      temp = os.environ['TEMP']
      zipped = os.path.join(temp, filename)
      unzipped = os.path.join(temp, 'ExportCHB.xml')
      urllib.URLopener().retrieve(url, zipped)

      with gzip.open(zipped, 'rb') as f_in, open(unzipped, 'wb') as f_out:
          shutil.copyfileobj(f_in, f_out)
Shutdown Python:
      import os, datetime

      filename = 'ExportCHB' + datetime.datetime.now().strftime("%Y%m%d") + '010001.xml.gz'
      temp = os.environ['TEMP']
      zipped = os.path.join(temp, filename)
      unzipped = os.path.join(temp, 'ExportCHB.xml')

      os.remove(zipped)
      os.remove(unzipped)

Parameters:
- DestDataset_ESRISHAPE = ..\data\bushaltes.zip   # Destination Esri Shapefile Folder
- SourceDataset_WFS = https://geodata.nationaalgeoregister.nl/bestuurlijkegrenzen/wfs?   # Source WFS (Web Feature Service) URL

Readers:
- WFS_1: WFS from $(SourceDataset_WFS)
- XML_1: XML from ${TEMP}\ExportCHB.xml

Writers:
- ESRISHAPE_1: ESRISHAPE to $(DestDataset_ESRISHAPE)

Note: Centrale Halte Bestand (CHB) wordt in Python startup script gedownload. / Bron: http://data.ndovloket.nl/haltes/
quay (reader XML_1)
    attributes: mutationdate xml_char(21), onlygetout xml_char(6), quayaccessibilityadaptions.alightingpositionwidth xml_decimal(5,2), quayaccessibilityadaptions.bayentranceangles xml_decimal(6,2), quayaccessibilityadaptions.bayexitangles xml_decimal(6,2), quayaccessibilityadaptions.baylength xml_decimal(6,2), quayaccessibilityadaptions.boardingpositionwidth xml_decimal(5,2), quayaccessibilityadaptions.embaymentwidth xml_decimal(5,2), quayaccessibilityadaptions.fulllengthguideline xml_char(6), quayaccessibilityadaptions.groundsurfaceindicator xml_char(6), quayaccessibilityadaptions.guidelines xml_char(6), quayaccessibilityadaptions.guidelinestopplaceconnection xml_char(6), quayaccessibilityadaptions.heightwithenvironment xml_decimal(6,2), quayaccessibilityadaptions.kerbheight xml_decimal(4,2), quayaccessibilityadaptions.lift xml_char(6), quayaccessibilityadaptions.liftedpartlength xml_decimal(6,2), quayaccessibilityadaptions.markedkerb xml_char(6), quayaccessibilityadaptions.mutationdate xml_char(21), quayaccessibilityadaptions.narrowestpassagewidth xml_decimal(5,2), quayaccessibilityadaptions.quayshapetype xml_char(23), quayaccessibilityadaptions.ramp xml_char(6), quayaccessibilityadaptions.ramplength xml_decimal(6,2), quayaccessibilityadaptions.rampwidth xml_decimal(5,2), quayaccessibilityadaptions.stopplaceaccessroute xml_char(6), quayaccessibilityadaptions.tactilegroundsurfaceindicator xml_char(6), quayaccessibilityadaptions.validfrom xml_char(21), quaybearing.compassdirection xml_decimal(4,0), quaybearing.mutationdate xml_char(21), quaybearing.validfrom xml_char(21), quaycode xml_char(14),
      quayconcessionprovider.concessionprovidercode xml_char(5), quayconcessionprovider.mutationdate xml_char(21), quayconcessionprovider.validfrom xml_char(21), quaydisabledaccessible.disabledaccessible xml_char(2), quaydisabledaccessible.mutationdate xml_char(21), quaydisabledaccessible.transportmode xml_char(6), quaydisabledaccessible.validfrom xml_char(21), quaydisabledaccessible{}.disabledaccessible xml_char(2), quaydisabledaccessible{}.mutationdate xml_char(21), quaydisabledaccessible{}.transportmode xml_char(5), quaydisabledaccessible{}.validfrom xml_char(21), quayextraattributes.greenstop xml_char(6), quayextraattributes.hectometersign xml_decimal(8,0), quayextraattributes.liftedbicyclepath xml_char(6), quayextraattributes.mutationdate xml_char(21), quayextraattributes.roadcode xml_char(6), quayextraattributes.validfrom xml_char(21), quayfacilities.audiobutton xml_char(6), quayfacilities.bicycleparking xml_char(6), quayfacilities.bins xml_char(6), quayfacilities.illuminatedstop xml_char(6), quayfacilities.infounit xml_char(6), quayfacilities.leantosupport xml_char(6), quayfacilities.mutationdate xml_char(21), quayfacilities.numberofbicycleplaces xml_decimal(5,0), quayfacilities.ovccharging xml_char(6), quayfacilities.ovccico xml_char(6), quayfacilities.passengerinformationdisplay xml_char(6), quayfacilities.passengerinformationdisplaytype xml_decimal(4,0), quayfacilities.routenetworkmap xml_char(6),
      quayfacilities.seatavailable xml_char(6), quayfacilities.shelter xml_char(6), quayfacilities.shelterpublicity xml_char(6), quayfacilities.stopsign xml_char(6), quayfacilities.stopsigntype xml_char(21), quayfacilities.timetableinformation xml_char(6), quayfacilities.validfrom xml_char(21), quaylocationdata.level xml_decimal(2,0), quaylocationdata.location xml_char(101), quaylocationdata.mutationdate xml_char(21), quaylocationdata.rd-x xml_decimal(7,0), quaylocationdata.rd-y xml_decimal(7,0), quaylocationdata.rd-z xml_decimal(2,0), quaylocationdata.street xml_char(37), quaylocationdata.town xml_char(29), quaylocationdata.validfrom xml_char(21), quaymunicipality.municipalitycode xml_char(10), quaymunicipality.mutationdate xml_char(21), quaymunicipality.validfrom xml_char(21), quaynamedata.mutationdate xml_char(21), quaynamedata.quayname xml_char(36), quaynamedata.stopsidecode xml_char(9), quaynamedata.validfrom xml_char(21), quayowner.mutationdate xml_char(21), quayowner.quayownercode xml_char(11), quayowner.validfrom xml_char(21), quayremarks.mutationdate xml_char(21), quayremarks.remarks xml_char(471), quayremarks.remarkstatus xml_char(8), quayremarks.validfrom xml_char(21),
      quaystatusdata.mutationdate xml_char(21), quaystatusdata.quaystatus xml_char(10), quaystatusdata.validfrom xml_char(21), quaytransportmodes.transportmodedata.mutationdate xml_char(21), quaytransportmodes.transportmodedata.transportmode xml_char(6), quaytransportmodes.transportmodedata.validfrom xml_char(21), quaytransportmodes.transportmodedata{}.mutationdate xml_char(21), quaytransportmodes.transportmodedata{}.transportmode xml_char(5), quaytransportmodes.transportmodedata{}.validfrom xml_char(21), quaytypedata.mutationdate xml_char(21), quaytypedata.quaytype xml_char(17), quaytypedata.validfrom xml_char(21), quayvisuallyaccessible.mutationdate xml_char(21), quayvisuallyaccessible.validfrom xml_char(21), quayvisuallyaccessible.visuallyaccessible xml_char(2), stopinternalcode xml_char(11), stopobjectcode xml_char(11), validfrom xml_char(21), xml_fragment xml_xml, xml_id xml_char(23), xml_matched_element xml_char(5), xml_parent_child_pos xml_char(1), xml_parent_id xml_char(1)
    -> AttributeKeeper
Note: Provinciegrens Groningen ophalen / Bron: https://www.pdok.nl/nl/service/wfs-bestuurlijke-grenzen / Met behulp van XML Filter Expression alleen provincie Groningen selecteren
provincies (reader WFS_1)
    attributes: gml_parent_id xml_buffer, gml_parent_property xml_buffer, gml_id xml_buffer, gid xml_int32, gid.xsi_nil xml_boolean, provincienaam xml_buffer, provincienaam.xsi_nil xml_boolean, geom xml_geometry
    -> SpatialFilter [input 1]
AttributeManager
    ATTR_TABLE:
      RENAME_SET_VALUE mutationdate > mutation
      RENAME_SET_VALUE quaynamedata.quayname > quayname
      RENAME_SET_VALUE quayowner.quayownercode > quayowner
      RENAME_SET_VALUE quaystatusdata.quaystatus > quaystatus
      RENAME_SET_VALUE quaydisabledaccessible.disabledaccessible > accessible
      RENAME_SET_VALUE quayfacilities.bicycleparking > bicyclepar
      RENAME_SET_VALUE quayfacilities.bins > bins
      RENAME_SET_VALUE quayfacilities.shelter > shelter
      REMOVE quaylocationdata.rd-x
      REMOVE quaylocationdata.rd-y
      REMOVE gml_parent_id
      REMOVE gml_parent_property
      REMOVE gml_id
      REMOVE geom
      REMOVE _predicate
      REMOVE gid
      REMOVE gid.xsi_nil
      REMOVE provincienaam
      REMOVE provincienaam.xsi_nil
    -> bushaltes_in_de_provincie (writer ESRISHAPE_1)
    -> TestFilter_2
bushaltes_in_de_provincie (writer ESRISHAPE_1)
    attributes: mutation char(21), quaycode char(14), quayname char(200), quayowner char(11), quaystatus char(200), accessible char(200), bicyclepar char(200), bins char(200), shelter char(200)
TestFilter_2
    TEST_LIST = BOOL_OP,OR,COMPOSITE_TEST,<Unused>,TEST_CLAUSE,"TEST @Value(quayowner) = P0020",Wegbeheerder provincie Groningen
    DEFAULT_VALUE = Overige wegbeheerders
    Wegbeheerder provincie Groningen -> bushaltes_van_de_provincie (writer ESRISHAPE_1)
Note: Gedownload bronbestand (.gz en .XML) wordt opgeruimd in Python shutdown script
bushaltes_van_de_provincie (writer ESRISHAPE_1)
    attributes: mutation char(21), quaycode char(14), quayname char(200), quayowner char(11), quaystatus char(200), accessible char(200), bicyclepar char(200), bins char(200), shelter char(200)

Bookmark: Filter attributen en features
AttributeKeeper
    KEEP_ATTRS = quayfacilities.bins,quaynamedata.quayname,quaystatusdata.quaystatus,quaycode,quayfacilities.bicycleparking,quayowner.quayownercode,mutationdate,quayfacilities.shelter,quaylocationdata.rd-x,quaylocationdata.rd-y,quaydisabledaccessible.disabledaccessible
    -> TestFilter
TestFilter
    TEST_LIST:
      BOOL_OP,OR,COMPOSITE_TEST,<Unused>,TEST_CLAUSE,"TEST @Value(quaystatusdata.quaystatus) = available
      TEST @Value(quaystatusdata.quaystatus) = unavailable",Beschikbaar of tijdelijk niet-beschikbaar
    DEFAULT_VALUE = Gepland of vervallen
    Beschikbaar of tijdelijk niet-beschikbaar -> VertexCreator

Bookmark: Maak geometrie (RD New)
VertexCreator
    YVAL = @Value(quaylocationdata.rd-y)
    XVAL = @Value(quaylocationdata.rd-x)
    MODE_NAME = Add Point
    -> CoordinateSystemSetter
CoordinateSystemSetter
    COORDSYS = EPSG:28992
    -> SpatialFilter [input 2]

Bookmark: Filter op provinciegrens Groningen
SpatialFilter
    AGGREGATE_HANDLING = Yes
    PASS_CRITERIA = Pass Against One Filter
    CURVE_BOUNDARY_RULE_PARAM = Default Rule
    PREDICATES = INTERSECTS
    ATTR_ACCUM_MODE = Merge Filter
    ATTR_CONFLICT_RES = Use Candidate
    BASE_TYPE = Multiple Filters
    PREDATTR = _predicate
    USE_BOUNDING_BOX = No
    PASSED -> AttributeManager
